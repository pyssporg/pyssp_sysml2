package Aircraft {
  requirement def Requirement_REQ_Control {
    doc /* Provide full HOTAS pilot controls, digital fly-by-wire channels, and autopilot hold modes. */
  }

  requirement def Requirement_REQ_Waypoints_1 {
    doc /* It should support loading a number of waypoints that it should fly to in order. */
  }
}
