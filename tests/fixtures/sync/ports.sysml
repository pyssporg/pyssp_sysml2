package Example {
          port def Signal {
            attribute x: Real;
            attribute y: Real;
          }

          port def DebugSignal {
            attribute level: Integer;
          }
        }
