package Values {
          part def Values {
            attribute f : Real = 1.0;
            attribute i = 42;
            attribute s = "hi";
            attribute t = true;
            attribute f2 = false;
            attribute taps = (1.0, 2.0);
            attribute declared : Real;
          }
        }
