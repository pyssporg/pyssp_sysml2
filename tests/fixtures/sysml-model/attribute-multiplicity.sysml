package Values {
          part def Multi {
            attribute fixed : Real[3];
            attribute bounded : Integer[2..4];
            attribute unbounded : Real[0..*];
            attribute scalar : Real;
          }
        }
