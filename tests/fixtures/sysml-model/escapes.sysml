package Escapes {
          part def Text {
            attribute lines = "one\ntwo";
            attribute path = "C:\\temp\\new";
            attribute quote = "say \"hi\" now";
          }
        }
